/**
 * Invalid: Syntax errors test fixture
 * This file contains various syntax errors
 */
package SyntaxErrors {
    // Error: Missing name
    part def {
    }

    // Error: Missing semicolon
    part def NoSemicolon

    // Error: Unclosed brace
    part def Unclosed {
